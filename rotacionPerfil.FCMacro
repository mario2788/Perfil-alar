import Draft
import numpy as npy
import math as m

# parametros de operacion y geometricos
f = open( "/home/mario/Documentos/Perfil-alar/puntos_eppler420_Selig_format_dat.txt" )
vel_angular = 2500 # rmp
diam_int = 30 # mm
diam_ext = 80 # mm
largo = m.pi*diam_int/3*(1-0.1)   # mm

arrayNum = []
for i in range(1, 100):
	temp = f.readline().split()
	if ( len(temp) > 1 ) :
		[n1, n2] = temp
		arrayNum.append( [float(n1), float(n2), 0] )
	else:
		break

f.close()

# Escalado del perfil hasta el largo defido
arrayNum = npy.array( arrayNum )*largo

def proyec( radio ):
	# Proyeccion del plano al cilindro
	puntosCilindro = [] # (y,r,teta)
	for p in arrayNum:
	    puntosCilindro.append([ p[1],radio,p[0]/radio])
	
	# Cambio de coordenadas
	puntosCartecianos = [] # (x,y,z)
	for p in puntosCilindro:
	    puntosCartecianos.append([radio*m.cos(p[2]), p[0], radio*m.sin(p[2])])
	
	return puntosCartecianos

# crear documento:
name = "perfilAlar"
App.newDocument(name)
Gui.activeDocument().activeView().viewDefaultOrientation()

#seleccionar entorno:
Gui.activateWorkbench("DraftWorkbench")

# contruccion de la spline
def closeCurve( array3Dimesional ):
	points = []
	for index in range(0, len( array3Dimesional ) ) :
		points.append( FreeCAD.Vector( array3Dimesional[index] ) )

	spline = Draft.makeBSpline(points, closed=False, face=False, support=None)
	Draft.autogroup(spline)

while  diam_int  < diam_ext :
	closeCurve( proyec(diam_int/2) )
	#closeCurve( arrayNum )
	
	# Rotacion y traslado
	Draft.rotate([FreeCAD.ActiveDocument.BSpline], 25, FreeCAD.Vector(0.0, 0.0, 0.0), axis=FreeCAD.Vector(0.0, 0.0, 1.0), copy=True)
	#Draft.move([FreeCAD.ActiveDocument.BSpline001], FreeCAD.Vector(0.0, 0.0, 1.0), copy=False)
	diam_int = diam_int + 1



	

FreeCAD.ActiveDocument.recompute()
Gui.SendMsgToActiveView("ViewFit")
